module periodictableparser {
    yang-version 1;
    namespace "urn:opendaylight:params:xml:ns:yang:periodictableparser";
    prefix "periodictableparser";

    revision "2015-01-05" {
        description "Initial revision of periodictableparser model";
    }
}
